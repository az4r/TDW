(defun c:tdk_liczba_pretow ()
  (setq tdk_aktualna_liczba_pretow_rozstaw "150")
  (setq tdk_liczba_pretow_p1 (getpoint "\nWskaz poczatkowy punkt rozkladu"))
  (setq tdk_liczba_pretow_p2 (getpoint tdk_liczba_pretow_p1 "\nWskaz koncowy punkt rozkladu"))  
  
  (setq tdk_liczba_pretow_rozstaw (getstring (strcat "\nPodaj rozstaw pretow (mm): <" tdk_aktualna_liczba_pretow_rozstaw ">")))
  (if (equal tdk_liczba_pretow_rozstaw "")
      (setq tdk_liczba_pretow_rozstaw tdk_aktualna_liczba_pretow_rozstaw)
      (princ)
  )
  (setq tdk_aktualna_liczba_pretow_rozstaw tdk_liczba_pretow_rozstaw)
  
  (setq tdk_liczba_pretow_odleglosc (* (distance tdk_liczba_pretow_p1 tdk_liczba_pretow_p2) 1000))
  (if (equal (rtos 1) (rtos (- (/ tdk_liczba_pretow_odleglosc (atof tdk_liczba_pretow_rozstaw)) (fix (/ tdk_liczba_pretow_odleglosc (atof tdk_liczba_pretow_rozstaw))))))
    (progn
    (setq tdk_liczba_pretow_wynik (/ tdk_liczba_pretow_odleglosc (atof tdk_liczba_pretow_rozstaw)))
    (setq tdk_liczba_pretow_wynik_korekta 1)
    (setq tdk_liczba_pretow_wynik (+ tdk_liczba_pretow_wynik 1))
    )
    (progn
    (setq tdk_liczba_pretow_wynik (fix (1+ (/ tdk_liczba_pretow_odleglosc (atof tdk_liczba_pretow_rozstaw)))))
    (setq tdk_liczba_pretow_wynik_korekta 1)
    )
  )
  (setq tdk_liczba_pretow_dlugosc_rozkladu (/ (* (- tdk_liczba_pretow_wynik tdk_liczba_pretow_wynik_korekta) (atof tdk_liczba_pretow_rozstaw)) 1000))
  (princ (strcat "Liczba pretow w rozkladzie wynosi: " (rtos tdk_liczba_pretow_wynik 2 0) "\nWymagana dlugosc rozkladu dla tej liczby pretow wynosi: " (rtos tdk_liczba_pretow_dlugosc_rozkladu 2 4) "m"))
  (alert (strcat "Liczba pretow w rozkladzie wynosi: " (rtos tdk_liczba_pretow_wynik 2 0) "\nWymagana dlugosc rozkladu dla tej liczby pretow wynosi: " (rtos tdk_liczba_pretow_dlugosc_rozkladu 2 4) "m"))
  (princ)
)
