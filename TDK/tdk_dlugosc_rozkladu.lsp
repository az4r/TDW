(defun c:tdk_dlugosc_rozkladu ()
  
  
  (setq tdk_dlugosc_rozkladu_aktualna_liczba_pretow "1")
  (setq tdk_dlugosc_rozkladu_liczba_pretow (getstring (strcat "\nPodaj liczbe pretow: <" tdk_dlugosc_rozkladu_aktualna_liczba_pretow ">")))
  (if (equal tdk_dlugosc_rozkladu_liczba_pretow "")
      (setq tdk_dlugosc_rozkladu_liczba_pretow tdk_dlugosc_rozkladu_aktualna_liczba_pretow)
      (princ)
  )
  (setq tdk_dlugosc_rozkladu_liczba_pretow (atoi tdk_dlugosc_rozkladu_liczba_pretow))
  (setq tdk_dlugosc_rozkladu_aktualna_liczba_pretow tdk_dlugosc_rozkladu_liczba_pretow)
  
  (setq tdk_dlugosc_rozkladu_aktualny_rozstaw_pretow "150")
  (setq tdk_dlugosc_rozkladu_rozstaw_pretow (getstring (strcat "\nPodaj rozstaw pretow (mm): <"tdk_dlugosc_rozkladu_aktualny_rozstaw_pretow ">")))
  (if (equal tdk_dlugosc_rozkladu_rozstaw_pretow "")
      (setq tdk_dlugosc_rozkladu_rozstaw_pretow tdk_dlugosc_rozkladu_aktualny_rozstaw_pretow)
      (princ)
  )
  (setq tdk_dlugosc_rozkladu_rozstaw_pretow (atoi tdk_dlugosc_rozkladu_rozstaw_pretow))
  (setq tdk_dlugosc_rozkladu_aktualny_rozstaw_pretow tdk_dlugosc_rozkladu_rozstaw_pretow)
    
  (setq tdk_dlugosc_rozkladu_liczba_pretow (- tdk_dlugosc_rozkladu_liczba_pretow 1))
  (setq tdk_dlugosc_rozkladu_dlugosc_rozkladu (* tdk_dlugosc_rozkladu_liczba_pretow tdk_dlugosc_rozkladu_rozstaw_pretow))
  (princ (strcat "Dlugosc rozkladu wynosi: " (rtos (/ (float tdk_dlugosc_rozkladu_dlugosc_rozkladu) 1000) 2 4) "m"))
  (alert (strcat "Dlugosc rozkladu wynosi: " (rtos (/ (float tdk_dlugosc_rozkladu_dlugosc_rozkladu) 1000) 2 4) "m"))
  (princ)
)
