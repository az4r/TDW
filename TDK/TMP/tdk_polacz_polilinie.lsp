(defun c:tdk_polacz_polilinie ( / tdk_aktualny_tryb_podpowiedzi_konwersji_polilinii tdk_polacz_polilinie_selekcja )
  (setq tdk_aktualny_tryb_podpowiedzi_konwersji_polilinii (getvar 'PEDITACCEPT))
  (setvar 'PEDITACCEPT 1)
  (if (and (setq tdk_polacz_polilinie_selekcja (ssget "_:L" '((0 . "ARC,LINE,LWPOLYLINE")))) (setq tdk_polacz_polilinie_dlugosc_polaczenia (getdist "\nPodaj dlugosc polaczenia <0>: ")))
    (command "_.pedit" "_M" tdk_polacz_polilinie_selekcja "" "_J" "T" "O" tdk_polacz_polilinie_dlugosc_polaczenia "")
    (princ)
  )
  (setvar 'PEDITACCEPT tdk_aktualny_tryb_podpowiedzi_konwersji_polilinii)
)
