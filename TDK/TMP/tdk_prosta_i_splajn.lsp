(defun c:tdk_prosta_i_splajn( / *error* )
  (defun *error* ( tdk_przyczyna_bledu )
    (command-s)
    (command-s "_UCS" "_P")
    (setq tdk_prosta_i_splajn_ob1 nil)
    (setq tdk_prosta_i_splajn_ob2 nil)
    (setq tdk_prosta_i_splajn_rozstaw nil)
    (setq tdk_prosta_i_splajn_kierunek_rozstawu "")
    (setq tdk_prosta_i_splajn_operator "")
    (setq tdk_prosta_i_splajn_poczatek_rozstawu "")
    (setq tdk_prosta_i_splajn_koniec_rozstawu "")
    (setvar "DIMZIN" tdk_prosta_i_splajn_aktualna_wartosc_dimzin)
    (print (read "***PRZERWANO***"))
    (princ)
  )
  (command "_UCS" "_W")
  (setq tdk_prosta_i_splajn_aktualna_wartosc_dimzin (getvar "DIMZIN"))
  (setvar "DIMZIN" 0)
  (setq tdk_prosta_i_splajn_ob1 nil)
  (setq tdk_prosta_i_splajn_ob2 nil)
  (setq tdk_prosta_i_splajn_rozstaw nil)
  (setq tdk_prosta_i_splajn_kierunek_rozstawu "")
  (while (equal tdk_prosta_i_splajn_ob1 nil)
    (setq tdk_prosta_i_splajn_ob1 (entsel "\nWskaz pierwszy obiekt: "))
  )
  (while (equal tdk_prosta_i_splajn_ob2 nil)
    (setq tdk_prosta_i_splajn_ob2 (entsel "\nWskaz drugi obiekt: "))
  )
  (while (equal tdk_prosta_i_splajn_rozstaw nil)
    (setq tdk_prosta_i_splajn_rozstaw (getreal "\nPodaj rozstaw (m): "))
  )
  (while (equal tdk_prosta_i_splajn_kierunek_rozstawu "")
    (setq tdk_prosta_i_splajn_kierunek_rozstawu (getstring "\nWybierz kierunek (L/S/P): [L/S/P]"))
  )
  (setq tdk_prosta_i_splajn_punkt_wstawienia_tabeli (getpoint "\nWskaz punkt wstawienia tabeli: "))
  (setq tdk_prosta_i_splajn_przestrzen_modelu (vla-get-ModelSpace (vla-get-ActiveDocument (vlax-get-acad-object))))
  (setq tdk_prosta_i_splajn_ob1_p1 (cdr (assoc 10 (entget (car tdk_prosta_i_splajn_ob1)))))
  (setq tdk_prosta_i_splajn_ob1_p2 (cdr (assoc 11 (reverse (entget (car tdk_prosta_i_splajn_ob1))))))
  (setq tdk_prosta_i_splajn_ob2_p1 (cdr (assoc 10 (entget (car tdk_prosta_i_splajn_ob2)))))
  (setq tdk_prosta_i_splajn_ob2_p2 (cdr (assoc 11 (reverse (entget (car tdk_prosta_i_splajn_ob2))))))
  (if (equal (cdr (assoc 0 (entget (car tdk_prosta_i_splajn_ob1)))) "LWPOLYLINE")
    (progn
      (setq tdk_prosta_i_splajn_ob1_p1 (cdr (assoc 10 (entget (car tdk_prosta_i_splajn_ob1)))))
      (setq tdk_prosta_i_splajn_ob1_p2 (cdr (assoc 10 (reverse (entget (car tdk_prosta_i_splajn_ob1))))))
    )
    (princ)
  )
  (if (equal (cdr (assoc 0 (entget (car tdk_prosta_i_splajn_ob2)))) "LWPOLYLINE")
    (progn
      (setq tdk_prosta_i_splajn_ob2_p1 (cdr (assoc 10 (entget (car tdk_prosta_i_splajn_ob2)))))
      (setq tdk_prosta_i_splajn_ob2_p2 (cdr (assoc 10 (reverse (entget (car tdk_prosta_i_splajn_ob2))))))
    )
    (princ)
  )
  (if (< (car tdk_prosta_i_splajn_ob1_p1) (car tdk_prosta_i_splajn_ob1_p2))
    (setq tdk_prosta_i_splajn_ob1_pp tdk_prosta_i_splajn_ob1_p1)
    (setq tdk_prosta_i_splajn_ob1_pp tdk_prosta_i_splajn_ob1_p2)
  )
  (if (< (car tdk_prosta_i_splajn_ob2_p1) (car tdk_prosta_i_splajn_ob2_p2))
    (setq tdk_prosta_i_splajn_ob2_pp tdk_prosta_i_splajn_ob2_p1)
    (setq tdk_prosta_i_splajn_ob2_pp tdk_prosta_i_splajn_ob2_p2)
  )
  (if (> (car tdk_prosta_i_splajn_ob1_pp) (car tdk_prosta_i_splajn_ob2_pp))
    (setq tdk_prosta_i_splajn_poczatek_rozstawu tdk_prosta_i_splajn_ob1_pp)
    (setq tdk_prosta_i_splajn_poczatek_rozstawu tdk_prosta_i_splajn_ob2_pp)
  )
  (if (> (car tdk_prosta_i_splajn_ob1_p1) (car tdk_prosta_i_splajn_ob1_p2))
    (setq tdk_prosta_i_splajn_ob1_pk tdk_prosta_i_splajn_ob1_p1)
    (setq tdk_prosta_i_splajn_ob1_pk tdk_prosta_i_splajn_ob1_p2)
  )
  (if (> (car tdk_prosta_i_splajn_ob2_p1) (car tdk_prosta_i_splajn_ob2_p2))
    (setq tdk_prosta_i_splajn_ob2_pk tdk_prosta_i_splajn_ob2_p1)
    (setq tdk_prosta_i_splajn_ob2_pk tdk_prosta_i_splajn_ob2_p2)
  )
  (if (< (car tdk_prosta_i_splajn_ob1_pk) (car tdk_prosta_i_splajn_ob2_pk))
    (setq tdk_prosta_i_splajn_koniec_rozstawu tdk_prosta_i_splajn_ob1_pk)
    (setq tdk_prosta_i_splajn_koniec_rozstawu tdk_prosta_i_splajn_ob2_pk)
  )
  (setq tdk_prosta_i_splajn_dlugosc_obszaru (abs (- (car tdk_prosta_i_splajn_poczatek_rozstawu) (car tdk_prosta_i_splajn_koniec_rozstawu))))
  (setq tdk_prosta_i_splajn_liczba_rozstawow (1+ (fix (/ tdk_prosta_i_splajn_dlugosc_obszaru tdk_prosta_i_splajn_rozstaw))))
  (setq tdk_prosta_i_splajn_obszar_dzialania (* (1- tdk_prosta_i_splajn_liczba_rozstawow) tdk_prosta_i_splajn_rozstaw))
  (if (equal tdk_prosta_i_splajn_kierunek_rozstawu "L")
      (setq tdk_prosta_i_splajn_operator +)
      (princ)
  )
  (if (equal tdk_prosta_i_splajn_kierunek_rozstawu "S")
    (progn
      (setq tdk_prosta_i_splajn_operator +)
      (setq tdk_prosta_i_splajn_przesuniecie_rozstawu (/ (- tdk_prosta_i_splajn_dlugosc_obszaru tdk_prosta_i_splajn_obszar_dzialania) 2))
      (setq tdk_prosta_i_splajn_poczatek_rozstawu (subst (+ (car tdk_prosta_i_splajn_poczatek_rozstawu) tdk_prosta_i_splajn_przesuniecie_rozstawu) (car tdk_prosta_i_splajn_poczatek_rozstawu) tdk_prosta_i_splajn_poczatek_rozstawu))
      (setq tdk_prosta_i_splajn_koniec_rozstawu (subst (- (car tdk_prosta_i_splajn_koniec_rozstawu) tdk_prosta_i_splajn_przesuniecie_rozstawu) (car tdk_prosta_i_splajn_koniec_rozstawu) tdk_prosta_i_splajn_koniec_rozstawu))
    )
    (princ)
  )
  (if (equal tdk_prosta_i_splajn_kierunek_rozstawu "P")
    (progn
      (setq tdk_prosta_i_splajn_operator -)
      (setq tdk_prosta_i_splajn_lewy_poczatek_rozstawu tdk_prosta_i_splajn_poczatek_rozstawu)
      (setq tdk_prosta_i_splajn_poczatek_rozstawu tdk_prosta_i_splajn_koniec_rozstawu)
      (setq tdk_prosta_i_splajn_koniec_rozstawu tdk_prosta_i_splajn_lewy_poczatek_rozstawu)
    )
    (princ)
  )
  (setq tdk_prosta_i_splajn_tabela (vla-Addtable tdk_prosta_i_splajn_przestrzen_modelu (vlax-3d-point tdk_prosta_i_splajn_punkt_wstawienia_tabeli) 3 tdk_prosta_i_splajn_liczba_rozstawow 10 30))
  (command "_scale" (entlast) "" tdk_prosta_i_splajn_punkt_wstawienia_tabeli 0.01)
  (vla-settext tdk_prosta_i_splajn_tabela 0 0 "TABELA DLUGOSCI")
  (setq tdk_prosta_i_splajn_tabela_kolumna 0)
  (repeat tdk_prosta_i_splajn_liczba_rozstawow
    (command "_zoom" "_scale" "10000X")
    (command "_xline" tdk_prosta_i_splajn_poczatek_rozstawu (polar tdk_prosta_i_splajn_poczatek_rozstawu (/ PI 2) 200) "")
    (setq tdk_prosta_i_splajn_ob3 (entlast))
    (setq tdk_prosta_i_splajn_ob1_vla (vlax-ename->vla-object (car tdk_prosta_i_splajn_ob1)))
    (setq tdk_prosta_i_splajn_ob2_vla (vlax-ename->vla-object (car tdk_prosta_i_splajn_ob2)))
    (setq tdk_prosta_i_splajn_ob3_vla (vlax-ename->vla-object tdk_prosta_i_splajn_ob3))
    (setq tdk_prosta_i_splajn_punkt_przeciecia1 (vlax-safearray->list(vlax-variant-value(vla-intersectwith tdk_prosta_i_splajn_ob1_vla tdk_prosta_i_splajn_ob3_vla acExtendBoth))))
    (setq tdk_prosta_i_splajn_punkt_przeciecia2 (vlax-safearray->list(vlax-variant-value(vla-intersectwith tdk_prosta_i_splajn_ob2_vla tdk_prosta_i_splajn_ob3_vla acExtendBoth))))
    (command "_erase" (entlast) "")
    (command "_pline" tdk_prosta_i_splajn_punkt_przeciecia1 tdk_prosta_i_splajn_punkt_przeciecia2 "")
    (setq tdk_prosta_i_splajn_odleglosc (rtos (distance tdk_prosta_i_splajn_punkt_przeciecia1 tdk_prosta_i_splajn_punkt_przeciecia2) 2 3))
    (setq tdk_prosta_i_splajn_odleglosc (vl-string-subst "," "." tdk_prosta_i_splajn_odleglosc))
    (command "_zoom" "_scale" "0.0001X")
    (setq tdk_prosta_i_splajn_poczatek_rozstawu (subst (tdk_prosta_i_splajn_operator (car tdk_prosta_i_splajn_poczatek_rozstawu) tdk_prosta_i_splajn_rozstaw) (car tdk_prosta_i_splajn_poczatek_rozstawu) tdk_prosta_i_splajn_poczatek_rozstawu))
    (setq tdk_prosta_i_splajn_tabela_kolumna_licznik (1+ tdk_prosta_i_splajn_tabela_kolumna))
    (vla-settext tdk_prosta_i_splajn_tabela 1 tdk_prosta_i_splajn_tabela_kolumna tdk_prosta_i_splajn_tabela_kolumna_licznik)
    (vla-settext tdk_prosta_i_splajn_tabela 2 tdk_prosta_i_splajn_tabela_kolumna tdk_prosta_i_splajn_odleglosc)
    (setq tdk_prosta_i_splajn_tabela_kolumna (1+ tdk_prosta_i_splajn_tabela_kolumna))
  )
  (command "_UCS" "_P")
  (setq tdk_prosta_i_splajn_ob1 nil)
  (setq tdk_prosta_i_splajn_ob2 nil)
  (setq tdk_prosta_i_splajn_rozstaw nil)
  (setq tdk_prosta_i_splajn_kierunek_rozstawu "")
  (setq tdk_prosta_i_splajn_operator "")
  (setq tdk_prosta_i_splajn_poczatek_rozstawu "")
  (setq tdk_prosta_i_splajn_koniec_rozstawu "")
  (setvar "DIMZIN" tdk_prosta_i_splajn_aktualna_wartosc_dimzin)
  (princ)
)
