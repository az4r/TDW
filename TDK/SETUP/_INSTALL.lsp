(vla-load (vla-get-menugroups (vlax-get-acad-object)) "C:\\_PROJECTS\\TDK\\tdk.cuix")
(command "-PASEKN" "TDK" "H" "400,200" "1")
(command "-PASEKN" "TDK_SOFI" "H" "400,230" "1")
(princ "\n################### ZAINSTALOWANO TDK TOOLBAR ##################")
(princ)
