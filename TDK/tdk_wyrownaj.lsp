(defun c:tdk_wyrownaj()
  (setq tdk_wyrownaj_linia_odniesienia (car (entsel "\nWybierz linie odniesienia: ")))
  (setq tdk_wyrownaj_linia_odniesienia_p1 (cdr (assoc 10 (entget tdk_wyrownaj_linia_odniesienia))))
  (setq tdk_wyrownaj_linia_odniesienia_p2 (cdr (assoc 11 (entget tdk_wyrownaj_linia_odniesienia))))
  (setq tdk_wyrownaj_linia_odniesienia_a1 (/ (* (angle tdk_wyrownaj_linia_odniesienia_p1 tdk_wyrownaj_linia_odniesienia_p2) 180) PI))
  (setq tdk_wyrownaj_linia_odniesienia_a2 (/ (* (angle tdk_wyrownaj_linia_odniesienia_p2 tdk_wyrownaj_linia_odniesienia_p1) 180) PI))
   
  (repeat 100
  (setq tdk_wyrownaj_krawedz_linii (getpoint "\nWskaz krawedz linii wzgledem ktorej obrocic: "))
  (setq tdk_wyrownaj_linia_do_obrocenia (nentselp "" tdk_wyrownaj_krawedz_linii))
  ;(setq tdk_wyrownaj_linia_do_obrocenia (vlax-ename->vla-object (car tdk_wyrownaj_linia_do_obrocenia)))
  ;(setq tdk_wyrownaj_linia_do_obrocenia_p1 (vlax-curve-getStartPoint tdk_wyrownaj_linia_do_obrocenia))
  ;(setq tdk_wyrownaj_linia_do_obrocenia_p2 (vlax-curve-getEndPoint tdk_wyrownaj_linia_do_obrocenia))
  (setq tdk_wyrownaj_linia_do_obrocenia (car tdk_wyrownaj_linia_do_obrocenia))
  (setq tdk_wyrownaj_linia_do_obrocenia_p1 (cdr (assoc 10 (entget tdk_wyrownaj_linia_do_obrocenia))))
  (setq tdk_wyrownaj_linia_do_obrocenia_p2 (cdr (assoc 10 (reverse (entget tdk_wyrownaj_linia_do_obrocenia)))))
  
  (if (<= (distance tdk_wyrownaj_krawedz_linii tdk_wyrownaj_linia_do_obrocenia_p1) (distance tdk_wyrownaj_krawedz_linii tdk_wyrownaj_linia_do_obrocenia_p2))
    (progn
      (setq tdk_wyrownaj_linia_do_obrocenia_punkt_obrotu tdk_wyrownaj_linia_do_obrocenia_p1)
      (defun tdk_wyrownaj_linia_do_obrocenia_nowe_punkty()
        (setq tdk_wyrownaj_linia_do_obrocenia_przeniesiony_punkt_obrotu (cdr (assoc 10 (entget tdk_wyrownaj_linia_do_obrocenia))))
        (setq tdk_wyrownaj_linia_do_obrocenia_przeniesiony_koniec_linii (cdr (assoc 10 (reverse (entget tdk_wyrownaj_linia_do_obrocenia)))))
      )
      (setq tdk_wyrownaj_linia_do_obrocenia_koniec_linii tdk_wyrownaj_linia_do_obrocenia_p2)
    )
    (progn
      (setq tdk_wyrownaj_linia_do_obrocenia_punkt_obrotu tdk_wyrownaj_linia_do_obrocenia_p2)
      (defun tdk_wyrownaj_linia_do_obrocenia_nowe_punkty()
        (setq tdk_wyrownaj_linia_do_obrocenia_przeniesiony_punkt_obrotu (cdr (assoc 10 (reverse (entget tdk_wyrownaj_linia_do_obrocenia)))))
        (setq tdk_wyrownaj_linia_do_obrocenia_przeniesiony_koniec_linii (cdr (assoc 10 (entget tdk_wyrownaj_linia_do_obrocenia))))
      )
      (setq tdk_wyrownaj_linia_do_obrocenia_koniec_linii tdk_wyrownaj_linia_do_obrocenia_p1)
    )
  )
  (setq tdk_wyrownaj_linia_do_obrocenia_dlugosc (distance tdk_wyrownaj_linia_do_obrocenia_punkt_obrotu tdk_wyrownaj_linia_do_obrocenia_koniec_linii))
  
  (command "_align" tdk_wyrownaj_linia_do_obrocenia "" tdk_wyrownaj_linia_do_obrocenia_punkt_obrotu tdk_wyrownaj_linia_odniesienia_p1 tdk_wyrownaj_linia_do_obrocenia_koniec_linii tdk_wyrownaj_linia_odniesienia_p2 "" "_N")
  (tdk_wyrownaj_linia_do_obrocenia_nowe_punkty)
  (command "_ZOOM" "_SCALE" "10X")
  (command "_move" tdk_wyrownaj_linia_do_obrocenia "" tdk_wyrownaj_linia_do_obrocenia_przeniesiony_punkt_obrotu tdk_wyrownaj_krawedz_linii)
  (command "_ZOOM" "_SCALE" "0.1X")
  (tdk_wyrownaj_linia_do_obrocenia_nowe_punkty)
  (if (> (distance tdk_wyrownaj_linia_do_obrocenia_koniec_linii tdk_wyrownaj_linia_do_obrocenia_przeniesiony_koniec_linii) (* tdk_wyrownaj_linia_do_obrocenia_dlugosc 1.5))
    (command "_rotate" tdk_wyrownaj_linia_do_obrocenia "" tdk_wyrownaj_krawedz_linii 180)
    (princ)
  )
  )
)
